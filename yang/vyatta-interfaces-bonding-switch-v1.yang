module vyatta-interfaces-bonding-switch-v1 {
	namespace "urn:vyatta.com:mgmt:vyatta-interfaces-bonding-switch:1";
	prefix vyatta-interfaces-bonding-switch-v1;

	import configd-v1 {
		prefix configd;
	}
	import vyatta-interfaces-v1 {
		prefix if;
	}
	import vyatta-interfaces-bonding-v1 {
		prefix bonding;
	}
	import vyatta-interfaces-bridge-v1 {
		prefix br;
	}
	import vyatta-interfaces-switch-v1 {
		prefix sw;
	}
	import vyatta-vrrp-v1 {
		prefix vrrp;
	}

	organization "AT&T Inc.";
	contact
		"AT&T
		Postal: 208 S. Akard Street
			Dallas, TX 75202
		Web: www.att.com";

	description
		"Copyright (c) 2018, AT&T Intellectual Property.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 The YANG module for vyatta-interfaces-bonding-switch-v1";

	revision 2018-10-24 {
		description "Initial revision";
	}

	augment /if:interfaces/bonding:bonding {
		container switch-group {
			presence "Signals that this is a member of a switch";
			description
				"Used to add this interface to an existing switch and set the port
				 specific parameters associated with being a member of the switch.";
			configd:help "Add this interface to a switch";
			configd:end "vyatta-switch --action=process-slave -- --br-name=$VAR(switch/@) --if-name=$VAR(../@)";
			configd:priority 321;
			must 'not(../bonding:vif or ../br:bridge-group or ../bonding:address or ' +
			     '../vrrp:vrrp/vrrp:vrrp-group)' {
				error-message "switch-group member may not be supplied with vif, " +
					"bridge or routing protocols";
			}
			leaf switch {
				description "The switch of which this port is a member";
				configd:help "The switch of which this port is a member";
				configd:update "vyatta-switch --action=enslave-interface -- --br-name=$VAR(@) --if-name=$VAR(../../@)";
				configd:delete "vyatta-switch --action=remove-interface -- --br-name=$VAR(@) --if-name=$VAR(../../@)";
				mandatory true;
				type leafref {
					path /if:interfaces/sw:switch/sw:name;
				}
			}
			container port-parameters {
				presence "Specify per port parameters for this port";
				description "Override the defaul parameters for this port";
				configd:help "Override the defaul parameters for this port";
				uses sw:port-parameters {
					refine mode {
						mandatory true;
					}
				}
			}
		}
	}
}
